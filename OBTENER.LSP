;---------------------------------------------------------------------
(DEFUN HIERROMARCAT ()
  (setvar "blipmode" 0)
  (setq poder 0 PPLL "no" ttee "no")
  (CARGAR "C:llamarTX" "datext")   
  (setq entiHM (entsel "\nSelect a steel or a Mark : "))
  (if (= entiHM nil)
    (alert "   It has not been selected steel or mark   ")
    (progn
      (setq nentiHM (car entiHM))
      (setq propientiHM (entget nentiHM))
      (setq tipoHM (cdr (assoc 0 propientiHM)))
      (cond
        ((= tipoHM "TEXT")
          (c:llamarTX nentiHM)
          (if (/= tieneV nil)
            (progn
              (setq poder 1 ttee nentiHM)
              (setq s1 (handent WHPL))
              (if (/= s1 nil)
                (if (/= (entget s1) nil)
                  (setq PPLL s1)
                )
              )
            )
            (alert "   Text Mark Incorrect   ")
          )
        )
        ((= tipoHM "POLYLINE")
          (c:llamarPL nentiHM)
          (if (= tieneP nil)
            (alert "   Polyline Incorrect   ")
            (progn
              (setq s1 (handent WHNT))
              (if (= s1 nil)
                (alert "   You cannot edit Steel without Connection  ")
                (if (= (entget s1) nil)
                  (alert "   You cannot edit Steel without Connection  ")
                  (progn
                    (c:llamarTX s1)
                    (setq poder 1 ttee s1)
                    (setq s1 (handent WHPL))
                    (if (/= s1 nil)
                      (setq PPLL s1)
                    )
                  )
                )
              )
            )
          )
        )
        (T 
          (alert "   The object isn't Text and Polyline  ")
        )
      )
    )
  )
  
  (if (> poder 0)
    (progn
      (setq codigo  Wcodigo) 
      (setq Mfija   WMfija) 
      (setq Mmarca  WMmarca) 
      (setq Mglobal WMglobal) 
      (if (= poder 1)
        (setq Mtipo   WMtipo) 
        (setq Mtipo   WMTI) 
      )
      (setq fi      Wfi) 
      (setq numero  Wnumero) 
      (setq HPL     WHPL) 
      (setq HHTX     WHTX) 
      (setq reflejo Wreflejo)
      (setq posic   Wposic) 
      
      (setq fid  (itoa (- (length listfi)   (length (member fi listfi)))))
      (setq tipo (itoa (- (length listtipo) (length (member Mtipo listtipo)))))
      
      (cond
        ((= tipo "0")(setq aaa Wa11   ggg Wg11))
        ((= tipo "1")(setq aaa Wa11   ggg Wg11   rrr Wr11))
        ((= tipo "2")(setq aaa Wa11   bbb Wb11))
        ((= tipo "3")(setq aaa Wa11   bbb Wb11   ggg Wg11    rrr Wr11))
        ((= tipo "4")(setq aaa Wa11   bbb Wb11   ggg Wg11    rrr Wr11))
        ((= tipo "5")(setq aaa Wa11   bbb Wb11   ccc Wc11))
        ((= tipo "6")(setq aaa Wa11   bbb Wb11   ccc Wc11    ddd Wd11    eee We11    fff Wf11    ggg Wg11))
      )
        
      (if (/= PPLL "no")
        (progn
          (setq lista1 (ARMAR PPLL))
          (cond
            ((or (= tipo "0") (and (or (= tipo "1")(= tipo "3")(= tipo "4"))(< (atof ggg) 0.001)))
              (setq p1 (nth 0 lista1) p2 (nth 1 lista1))
            )
            ((and (= tipo "1")(> (atof ggg) 0.001))
              (setq p1 (nth 2 lista1) p2 (nth 3 lista1))
            )
            ((= tipo "2")
              (setq p1 (nth 1 lista1) p2 (nth 2 lista1))
            )
            ((and (= tipo "3")(> (atof ggg) 0.001))
              (setq p1 (nth 2 lista1) p2 (nth 3 lista1))
            )
            ((and (= tipo "4")(> (atof ggg) 0.001))
              (setq p1 (nth 2 lista1) p2 (nth 3 lista1))
            )
            ((= tipo "5")
              (setq p1 (nth 1 lista1) p2 (nth 2 lista1))
            )
          )
          (if (or (= reflejo 1)(= reflejo 4))
            (setq angulo (rtos (/ (* (angle p1 p2) 180) pi) 2 0))
            (setq angulo (rtos (/ (* (angle p2 p1) 180) pi) 2 0))
          )
        ) 
      )
      (if (and (= PPLL "no")(/= ttee "no"))
        (setq angulo (rtos (/ (* (cdr (assoc 50 (entget ttee))) 180) pi) 2 0))
      )
      (setq entext ttee enpoly PPLL)
      (if (= enpoly "no")(setq enpoly nil))
    )
  )
  
  (setvar "blipmode" blipmodeANT)
  
)

;---------------------------------------------------------------------
(DEFUN HIERROMARCA ()
  (setvar "blipmode" 0)
  (setq poder 0 PPLL "no" ttee "no")
  (CARGAR "C:llamarTX" "datext")   
  (setq entiHM (entsel "\nSelect a Steel or a Mark : "))
  (if (= entiHM nil)
    (alert "   It has not been selected steel or mark   ")
    (progn
      (setq nentiHM (car entiHM))
      (setq propientiHM (entget nentiHM))
      (setq tipoHM (cdr (assoc 0 propientiHM)))
      (cond
        ((= tipoHM "TEXT")
          (c:llamarTX nentiHM)
          (if (/= tieneV nil)
            (progn
              (setq poder 1 ttee nentiHM)
              (setq s1 (handent WHPL))
              (if (/= s1 nil)
                (if (/= (entget s1) nil)
                  (setq PPLL s1)
                )
              )
            )
            (alert "   Mark Text Incorrect   ")
          )
        )
        ((= tipoHM "POLYLINE")
          (c:llamarPL nentiHM)
          (if (= tieneP nil)
            (alert "   Polyline Incorrect   ")
            (progn
              (setq s1 (handent WHNT))
              (if (= s1 nil)
                (progn
                  (c:llamarPL nentiHM)
                  (setq poder 2)
                  (setq PPLL nentiHM)
                )
                (progn
                  (c:llamarTX s1)
                  (setq poder 1 ttee s1)
                  (setq s1 (handent WHPL))
                  (if (/= s1 nil)
                    (setq PPLL s1)
                  )
                )
              )
            )
          )
        )
        (T 
          (alert "   The object isn't Text and Polyline  ")
        )
      )
    )
  )
  
  (if (> poder 0)
    (progn
      ;(setq codigo  Wcodigo) 
      ;(setq Mfija   WMfija) 
      ;(setq Mmarca  WMmarca) 
      ;(setq Mglobal WMglobal) 
      (if (= poder 1)
        (setq Mtipo   WMtipo) 
        (setq Mtipo   WMTI) 
      )
      (setq fi      Wfi) 
      ;(setq numero  Wnumero) 
      ;(setq HPL     WHPL) 
      ;(setq HTX     WHTX) 
      (setq reflejo Wreflejo)
      (setq posic   Wposic) 
      
      (setq fid  (itoa (- (length listfi)   (length (member fi listfi)))))
      (setq tipo (itoa (- (length listtipo) (length (member Mtipo listtipo)))))
      
      (cond
        ((= tipo "0")(setq aaa Wa11   ggg Wg11))
        ((= tipo "1")(setq aaa Wa11   ggg Wg11   rrr Wr11))
        ((= tipo "2")(setq aaa Wa11   bbb Wb11))
        ((= tipo "3")(setq aaa Wa11   bbb Wb11   ggg Wg11    rrr Wr11))
        ((= tipo "4")(setq aaa Wa11   bbb Wb11   ggg Wg11    rrr Wr11))
        ((= tipo "5")(setq aaa Wa11   bbb Wb11   ccc Wc11))
        ((= tipo "6")(setq aaa Wa11   bbb Wb11   ccc Wc11    ddd Wd11    eee We11    fff Wf11    ggg Wg11))
      )
        
      (if (/= PPLL "no")
        (progn
          (setq lista1 (ARMAR PPLL))
          (cond
            ((or (= tipo "0") (and (or (= tipo "1")(= tipo "3")(= tipo "4"))(< (atof ggg) 0.001)))
              (setq p1 (nth 0 lista1) p2 (nth 1 lista1))
            )
            ((and (= tipo "1")(> (atof ggg) 0.001))
              (setq p1 (nth 2 lista1) p2 (nth 3 lista1))
            )
            ((= tipo "2")
              (setq p1 (nth 1 lista1) p2 (nth 2 lista1))
            )
            ((and (= tipo "3")(> (atof ggg) 0.001))
              (setq p1 (nth 2 lista1) p2 (nth 3 lista1))
            )
            ((and (= tipo "4")(> (atof ggg) 0.001))
              (setq p1 (nth 2 lista1) p2 (nth 3 lista1))
            )
            ((= tipo "5")
              (setq p1 (nth 1 lista1) p2 (nth 2 lista1))
            )
          )
          (if (or (= reflejo 1)(= reflejo 4))
            (setq angulo (rtos (/ (* (angle p1 p2) 180) pi) 2 0))
            (setq angulo (rtos (/ (* (angle p2 p1) 180) pi) 2 0))
          )
        ) 
      )
      (if (and (= PPLL "no")(/= ttee "no"))
        (setq angulo (rtos (/ (* (cdr (assoc 50 (entget ttee))) 180) pi) 2 0))
      )
    )
  )
  
  (setvar "blipmode" blipmodeANT)
  
)

;---------------------------------------------------------------------
(DEFUN C:EST33 ()
  (setq pip 0)
  (if (= mensajes "1")(alert "   Choose the Stirrups   "))
  (setq s1 (ssget (list (cons 8 layerest))))
  (if (= s1 nil)
    (setq valor numero pip 1)
    (progn
      (setq valor (itoa (sslength s1)))
      (if (= valor "0")(setq valor numero pip 1))
    )
  )
  (if (= pip 1)
    (if (= mensajes "1")(alert "   Stirrups has not been counted   "))
    (if (= mensajes "1")(alert (strcat "   It has not been counted " valor " Stirrups   ")))
  )
  valor
)

;---------------------------------------------------------------------
(DEFUN C:POS33 ()
  (setq pip 0)
  (if (= mensajes "1")(alert "   Select Line that it contains Slab Marks   "))
  (setq e1 (entsel "\nPicar Select Line that it contains Slab Marks : "))
  (if (= e1 nil)
    (setq valor numero pip 1)
    (progn
      (setq propie1 (entget (car e1)))
      (setq tipoe1 (cdr (assoc 0 propie1)))
      (if (/= tipoe1 "LINE")
        (setq valor numero pip 1)
        (progn
          (setq p1 (cdr (assoc 10 propie1)))
          (setq p2 (cdr (assoc 11 propie1)))
          (setq s1 (ssget "f" (list p1 p2) (list (cons 8 layerpos))))
          (if (= s1 nil)
            (setq valor numero pip 1)
            (progn
              (setq valor (itoa (sslength s1)))
              (if (= valor "0")(setq valor numero pip 1))
            )
          )
        )
      )
    )
  )
  (if (= pip 1)
    (if (= mensajes "1")(alert "   Stirrups has not been counted   "))
    (if (= mensajes "1")(alert (strcat "   It has not been counted " valor " Slab Marks   ")))
  )
  valor
)

;---------------------------------------------------------------------
(DEFUN C:OBT33 ()
  (setq pip 0)
  (if (= tipoabc "0")(setq abc "a"))
  (if (= tipoabc "1")(setq abc "b"))
  (if (= tipoabc "2")(setq abc "c"))
  (if (= tipoabc "3")(setq abc "d"))
  (if (= tipoabc "4")(setq abc "e"))
  (if (= tipoabc "5")(setq abc "f"))
  (if (= tipoabc "6")(setq abc "g"))
  
  (if (= tipoabc "7")
    (if (= mensajes "1")(alert (strcat "   Obtain angle_" "   ")))
    (if (= mensajes "1")(alert (strcat "   Obtain Distance " abc "   ")))
  ) 
  
  (if (= tipoabc "7")
    (progn
      (setq v (getangle "\nEnter Angle_ : "))
      (if (= v nil)
        (NOPONER)
        (setq valor (rtos (/ (* v 180) pi) 2 0))
      )
    )
    (progn
      (setq v (getdist "\nEnter Distance : "))
      (if (= v nil)
        (NOPONER)
        (setq valor (rtos v 2 2))
      )
    )
  )
  
  (if (= pip 1)
    (if (= tipoabc "7")
      (if (= mensajes "1")(alert "   The Angle_ has not been obtained   "))
      (if (= mensajes "1")(alert "   The Distance has not been obtained   "))
    )
    (if (= tipoabc "7")
      (if (= mensajes "1")(alert (strcat "   The Angle_ has been obtained = " valor "   ")))
      (if (= mensajes "1")(alert (strcat "   The Angle_ has been obtained " abc " = " valor "   ")))
    )
  )
 valor
)

;---------------------------------------------------------------------
(DEFUN NOPONER ()
  (if (= tipoabc "0")(setq valor aaa    pip 1))
  (if (= tipoabc "1")(setq valor bbb    pip 1))
  (if (= tipoabc "2")(setq valor ccc    pip 1))
  (if (= tipoabc "3")(setq valor ddd    pip 1))
  (if (= tipoabc "4")(setq valor eee    pip 1))
  (if (= tipoabc "5")(setq valor fff    pip 1))
  (if (= tipoabc "6")(setq valor ggg    pip 1))
  (if (= tipoabc "7")(setq valor angulo pip 1))
)
